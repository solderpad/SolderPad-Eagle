#require 4.1105

#usage "en: <b>Export a Bill Of Materials as JSON</b>\n"
	"<p>"
	" Saves a project's <i>Bill Of Material</i> as a <i>project</i>.json"
	" suitable for uploading to http://solderpad.com"
	" <author>Author: psd@solderpad.com</author>"
	"</p>";

if (!schematic) {
	dlgMessageBox(usage + "<hr><b>ERROR: No schematic!</b><p>\nThis program can only work in the schematic editor.");
	exit(1);
}

string escape(string s) {
char c = '"';
int pos = 0;
string tp;

	while ((pos = strchr(s, c, pos)) > -1) {
		tp = strsub(s, 0, pos);
		tp += "\\";
		tp += strsub(s, pos);
		s = tp;
		pos += 2;
	}
	return s;
}

schematic(SCH) {
	string FileName;
	string json;
	string sep = "";

	FileName = filesetext("bom", ".json");

	output(FileName, "wt") {
		printf("{\n");
		printf("\t\"items\": [\n");
		SCH.parts(P) {
			if (P.device.package) {
				json = sep + "\t\t{\n"
					+ "\t\t\t\"designator\": \"" + escape(P.name) + "\",\n"
					+ "\t\t\t\"value\": \"" + escape(P.value) + "\",\n"
					+ "\t\t\t\"description\": \"" + escape(P.device.headline) + "\"\n"
				    + "\t\t}";
				sep = ",\n";
				printf("%s", json);
			}
		}
		printf("\n\t]\n}\n");
	}
}
